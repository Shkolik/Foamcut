import FreeCAD, Draft, Part
from PySide import QtCore
from PySide import QtGui
import os

# - Get document object
doc = FreeCAD.activeDocument()

# - Get CNC configuration
config = doc.getObjectsByLabel('Config')[0]

'''
  Synchronize direction of two edges using their end vertexes
  @return (vertex00, vertex01, vertex10, vertex11)
'''
def getSynchronizedVertices(first, second):
  dist, vectors, info = first.distToShape(second)
  v1, v2 = vectors[0]
  return (
    first.firstVertex()   if first.firstVertex().Point == v1  else first.lastVertex(),
    first.lastVertex()    if first.firstVertex().Point == v1  else first.firstVertex(),
    second.firstVertex()  if second.firstVertex().Point == v2 else second.lastVertex(),
    second.lastVertex()   if second.firstVertex().Point == v2 else second.firstVertex(),
  )

class Route:
  def __init__(this, obj):
    obj.addProperty("App::PropertyPythonObject",  "Data", "", "", 5)
    obj.addProperty("App::PropertyString",        "Type", "", "", 5)
    obj.setEditorMode("Group", 3)
    obj.Data  = None
    obj.Type  = "Route"
    obj.Proxy = this

  def onChanged(this, fp, prop):
    #FreeCAD.Console.PrintMessage("Change property: " + str(prop) + "\n")
    pass

  def execute(this, obj):
    pass

  def __getstate__(self):
      pass #return {"name": self.Object.Name}

  def __setstate__(self, state):
      pass #self.Object = FreeCAD.ActiveDocument.getObject(state["name"])
      return None

class RouteVP:
  def __init__(this, obj):
      obj.Proxy = this

  def attach(this, obj):
    this.Object = obj.Object

  def getIcon(self):
      '''Return the icon in XPM format which will appear in the tree view. This method is\
              optional and if not defined a default icon is shown.'''
      return """
        /* XPM */
        static char * route_xpm[] = {
        "16 16 2 1",
        " 	c None",
        ".	c #000000",
        "                ",
        "             .. ",
        "            ....",
        "            .  .",
        "     ..     ....",
        "    ....    ..  ",
        "    .  .    .   ",
        "    ....   .    ",
        "    ..  ....    ",
        "   ..   .. .    ",
        "   .    .. .    ",
        "....     ...    ",
        ".  .            ",
        "....            ",
        " ..             ",
        "                "};
      """

  def __getstate__(self):
      pass #return {"name": self.Object.Name}

  def __setstate__(self, state):
      pass #self.Object = FreeCAD.ActiveDocument.getObject(state["name"])
      return None

def join():
  # - Check is common point for two lines
  def isCommonPoint(first, second):
    return True if first.distanceToPoint(second) < 0.6 else False


  # - Route entry object
  class RouteEntry:
    def __init__(this):
      this.Object   = None
      this.Reversed = False
      this.Length_L = float(0)
      this.Length_R = float(0)

    def toJSON(this):
      return json.dumps(this, default=lambda o: o.__dict__, sort_keys=True, indent=4)


  # - Get selected objects
  objects = [item.Object for item in Gui.Selection.getSelectionEx()]

  # - Check objects count
  if len(objects) == 0:
    print("ERROR: No objects selected")
    return

  # - Check objects
  size = 0
  for obj in objects:
    if not hasattr(obj, "Type") or (obj.Type != "Path" and obj.Type != "Rotation" and obj.Type != "Enter" and obj.Type != "Exit" and obj.Type != "Move" and obj.Type != "Join"):
      print ("ERROR: Not supported input")
      return

  # - Join path
  first       = objects[0]
  reversed    = None        # - Second segment is reversed
  START       = 0           # - Segment start point index
  END         = -1          # - Segment end point index
  route_data  = []
  item_index  = 0

  # - Check is single element
  if len(objects) == 1:
    # - Store element
    entry = RouteEntry()
    entry.Object    = first
    entry.Reversed  = False
    route_data.append(entry)

  # - Walk through other objects
  for second in objects[1:]:
    # - Add item index
    item_index = item_index + 1

    # - Process skipped element
    if first is None:
      first = second

      if first.Type == "Enter":
        entry = RouteEntry()
        entry.Object    = first
        entry.Reversed  = False
        route_data.append(entry)

      print("SKIP: %s" % second.Type)
      continue

    # - Skip rotation object
    if first.Type == "Rotation":
      print("R1")
      # - Store first element
      entry = RouteEntry()
      entry.Object    = first
      entry.Reversed  = False
      route_data.append(entry)

      # - Check if rotation is first element
      if item_index == 1:
        # - Do no skip next element
        first = second
        continue
      else:
        # - Go to next object
        first = None
        continue
    elif second.Type == "Rotation":
      print("R1 - 2")
      # - Store element
      entry = RouteEntry()
      entry.Object    = second
      entry.Reversed  = False
      route_data.append(entry)

      # - Skip element
      first = None
      continue


    elif first.Type == "Exit" and second.Type == "Enter":
      print("EXIT -> ENTER")

      # - Store first item
      if len(route_data) == 0:
        # - Store element
        entry = RouteEntry()
        entry.Object    = first
        entry.Reversed  = False
        route_data.append(entry)

      # - Store element
      entry = RouteEntry()
      entry.Object    = second
      entry.Reversed  = False
      route_data.append(entry)

      first = second
      continue




    # - Get lines on left plane
    if first.Type   == "Path":    first_line  = first.Path_L
    elif first.Type == "Enter":   first_line  = [App.Vector(-config.FieldWidth / 2, first.PointXL, first.PointZL)]
    elif first.Type == "Move":    first_line  = [
      App.Vector(-config.FieldWidth / 2, first.PointXL, first.PointZL),
      App.Vector(-config.FieldWidth / 2, first.PointXL + float(first.OffsetX), first.PointZL + float(first.OffsetZ))
    ]
    elif first.Type == "Join":    first_line  = [
      App.Vector(-config.FieldWidth / 2, first.PointXLA, first.PointZLA),
      App.Vector(-config.FieldWidth / 2, first.PointXLB, first.PointZLB)
    ]
    else:
      print("Unsupported first element")
      print(first.Label)
      print(second.Label)
      return

    if second.Type == "Path":   second_line = second.Path_L
    elif second.Type == "Exit": second_line = [App.Vector(-config.FieldWidth / 2, second.PointXL, second.PointZL)]
    elif second.Type == "Move": second_line = [
      App.Vector(-config.FieldWidth / 2, second.PointXL, second.PointZL),
      App.Vector(-config.FieldWidth / 2, second.PointXL + float(second.OffsetX), second.PointZL + float(second.OffsetZ))
    ]
    elif second.Type == "Join":    second_line  = [
      App.Vector(-config.FieldWidth / 2, second.PointXLA, second.PointZLA),
      App.Vector(-config.FieldWidth / 2, second.PointXLB, second.PointZLB)
    ]
    else:
      print("Unsupported second element")
      return

    if reversed is None:
      first_reversed = False

      # - Detect first pair
      if isCommonPoint(first_line[END], second_line[START]):
        print ("First connected: FWD - FWD")
        reversed = False
      elif isCommonPoint(first_line[END], second_line[END]):
        print ("First connected: FWD - REV")
        reversed = True
      elif isCommonPoint(first_line[START], second_line[START]):
        print ("First connected: REV - FWD")
        first_reversed  = True
        reversed        = False
      elif isCommonPoint(first_line[START], second_line[END]):
        print ("First connected: REV - REV")
        first_reversed  = True
        reversed        = True
      else:
        print("ERROR: [%s] not connected with [%s]" % (first.Label, second.Label))
        return

      # - Store first element
      entry = RouteEntry()
      entry.Object    = first
      entry.Reversed  = first_reversed
      entry.Length_L  = first.Length_L
      entry.Length_R  = first.Length_R
      route_data.append(entry)

      # - Store second element
      entry = RouteEntry()
      entry.Object    = second
      entry.Reversed  = reversed
      entry.Length_L  = second.Length_L
      entry.Length_R  = first.Length_R
      route_data.append(entry)

    else:
      # - Detect next pairs
      if isCommonPoint(first_line[START if reversed else END], second_line[START]):
        print ("Connected: FWD - FWD")
        reversed = False
      elif isCommonPoint(first_line[START if reversed else END], second_line[END]):
        print ("Connected: FWD - REV")
        reversed = True
      else:
        print("ERROR: [%s] not connected with [%s]" % (first.Label, second.Label))
        return

      # - Store next element
      entry = RouteEntry()
      entry.Object    = second
      entry.Reversed  = reversed
      entry.Length_L  = second.Length_L
      route_data.append(entry)

    # - Go to next object
    first = second

  # - Make route object
  route = doc.addObject("App::DocumentObjectGroupPython", "Route")
  Route(route)
  RouteVP(route.ViewObject)

  # - Put objects inside group
  route.Group = [item.Object for item in route_data]
  route.Data  = route_data

# - Process
join()
